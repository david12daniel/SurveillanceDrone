// ════════════════════════════════════════════════════════════════════
// AUTO-GENERATED by analysis/flight_time_model.py — DO NOT EDIT BY HAND.
// Regenerate:  python analysis/flight_time_model.py
//
// Holistic endurance sweep — 34 total buildable configurations.
// This instance table holds the BASELINE + top 34 by max flight time;
// the COMPLETE per-instance set (all components + battery attrs + flight
// time) is in flight_time_results.csv.
// Model: rotors=4, rho=1.225, FoM=0.65, eta=0.8, Cd=1.0, cruise=2.23 m/s, wind=4.5 m/s.
// Inclusion logic: airframe-bundled VTX/FPV/GPS/RX add power only (mass is in
// the airframe weight); non-bundled peripherals add mass+power. FPV/GPS/RX held
// at lightest reps (fpv=FpvCamBundled, gps=GpsBundled, rx=RxBundled); VTX swept when not bundled.
// ════════════════════════════════════════════════════════════════════
package FlightTimeAnalysis {
 private import ScalarValues::*;

 part def FlightTimeResult {
  attribute configId : String;
  attribute airframeId : String;
  attribute airframe : String;
  attribute battery : String;
  attribute chemistry : String;
  attribute cellCountS : Integer;
  attribute capacity_mAh : Real;
  attribute packVoltage_V : Real;
  attribute batteryMass_g : Real;
  attribute usableEnergy_Wh : Real;
  attribute thermalCam : String;
  attribute sbc : String;
  attribute dvr : String;
  attribute vtx : String;
  attribute fpv : String;
  attribute gps : String;
  attribute rx : String;
  attribute addedPayloadMass_g : Real;
  attribute totalPayloadPower_W : Real;
  attribute allUpMass_g : Real;
  attribute hoverPower_W : Real;
  attribute maxFlightTimeHover_min : Real;
  attribute flightTimeCruise_min : Real;
  attribute flightTimeHeadwind_min : Real;
  attribute hoverThrottle_pct : Real;
  attribute meetsR6_30min : Boolean;
  attribute meetsR8_60min : Boolean;
  attribute flyable : Boolean;
  attribute droneCost_USD : Real;
  attribute gcsCost_USD : Real;
  attribute totalSystemCost_USD : Real;
  attribute endurancePer1000USD : Real;
  attribute meetsBudgetR4 : Boolean;
 }

 // ── Recommended baseline (best flyable config meeting R6) ──
 part baseline : FlightTimeResult {
  :>> configId = "C000008";
  :>> airframeId = "AF3a";
  :>> airframe = "iFlight Chimera9 ECO";
  :>> battery = "Lumenier NAV 12000mAh 6S 21700 Amprius";
  :>> chemistry = "Li-ion";
  :>> cellCountS = 6;
  :>> capacity_mAh = 12000.0;
  :>> packVoltage_V = 22.2;
  :>> batteryMass_g = 920.0;
  :>> usableEnergy_Wh = 226.4;
  :>> thermalCam = "T13";
  :>> sbc = "SBC3";
  :>> dvr = "—";
  :>> vtx = "included";
  :>> fpv = "included";
  :>> gps = "included";
  :>> rx = "RxBundled";
  :>> addedPayloadMass_g = 95.0;
  :>> totalPayloadPower_W = 16.93;
  :>> allUpMass_g = 1744.0;
  :>> hoverPower_W = 231.4;
  :>> maxFlightTimeHover_min = 58.7;
  :>> flightTimeCruise_min = 60.3;
  :>> flightTimeHeadwind_min = 72.3;
  :>> hoverThrottle_pct = 14.9;
  :>> meetsR6_30min = true;
  :>> meetsR8_60min = false;
  :>> flyable = true;
  :>> droneCost_USD = 1533.48;
  :>> gcsCost_USD = 175.45;
  :>> totalSystemCost_USD = 1708.93;
  :>> endurancePer1000USD = 34.36;
  :>> meetsBudgetR4 = true;
 }

 // ── Top 34 configurations by max flight time ──
 part inst_C000008 : FlightTimeResult {
  :>> configId = "C000008";
  :>> airframeId = "AF3a";
  :>> airframe = "iFlight Chimera9 ECO";
  :>> battery = "Lumenier NAV 12000mAh 6S 21700 Amprius";
  :>> chemistry = "Li-ion";
  :>> cellCountS = 6;
  :>> capacity_mAh = 12000.0;
  :>> packVoltage_V = 22.2;
  :>> batteryMass_g = 920.0;
  :>> usableEnergy_Wh = 226.4;
  :>> thermalCam = "T13";
  :>> sbc = "SBC3";
  :>> dvr = "—";
  :>> vtx = "included";
  :>> fpv = "included";
  :>> gps = "included";
  :>> rx = "RxBundled";
  :>> addedPayloadMass_g = 95.0;
  :>> totalPayloadPower_W = 16.93;
  :>> allUpMass_g = 1744.0;
  :>> hoverPower_W = 231.4;
  :>> maxFlightTimeHover_min = 58.7;
  :>> flightTimeCruise_min = 60.3;
  :>> flightTimeHeadwind_min = 72.3;
  :>> hoverThrottle_pct = 14.9;
  :>> meetsR6_30min = true;
  :>> meetsR8_60min = false;
  :>> flyable = true;
  :>> droneCost_USD = 1533.48;
  :>> gcsCost_USD = 175.45;
  :>> totalSystemCost_USD = 1708.93;
  :>> endurancePer1000USD = 34.36;
  :>> meetsBudgetR4 = true;
 }

 part inst_C000025 : FlightTimeResult {
  :>> configId = "C000025";
  :>> airframeId = "AF4a";
  :>> airframe = "DarwinFPV X9";
  :>> battery = "Lumenier NAV 12000mAh 6S 21700 Amprius";
  :>> chemistry = "Li-ion";
  :>> cellCountS = 6;
  :>> capacity_mAh = 12000.0;
  :>> packVoltage_V = 22.2;
  :>> batteryMass_g = 920.0;
  :>> usableEnergy_Wh = 226.4;
  :>> thermalCam = "T13";
  :>> sbc = "SBC3";
  :>> dvr = "—";
  :>> vtx = "included";
  :>> fpv = "included";
  :>> gps = "GpsBundled";
  :>> rx = "RxBundled";
  :>> addedPayloadMass_g = 95.0;
  :>> totalPayloadPower_W = 16.93;
  :>> allUpMass_g = 1762.0;
  :>> hoverPower_W = 234.7;
  :>> maxFlightTimeHover_min = 57.9;
  :>> flightTimeCruise_min = 59.4;
  :>> flightTimeHeadwind_min = 71.3;
  :>> hoverThrottle_pct = 13.6;
  :>> meetsR6_30min = true;
  :>> meetsR8_60min = false;
  :>> flyable = true;
  :>> droneCost_USD = 1459.48;
  :>> gcsCost_USD = 175.45;
  :>> totalSystemCost_USD = 1634.93;
  :>> endurancePer1000USD = 35.4;
  :>> meetsBudgetR4 = true;
 }

 part inst_C000009 : FlightTimeResult {
  :>> configId = "C000009";
  :>> airframeId = "AF3a";
  :>> airframe = "iFlight Chimera9 ECO";
  :>> battery = "Upgrade Energy GREEN V2 6S3P 12Ah Amprius SA10";
  :>> chemistry = "Li-ion";
  :>> cellCountS = 6;
  :>> capacity_mAh = 12000.0;
  :>> packVoltage_V = 21.6;
  :>> batteryMass_g = 919.0;
  :>> usableEnergy_Wh = 220.3;
  :>> thermalCam = "T13";
  :>> sbc = "SBC3";
  :>> dvr = "—";
  :>> vtx = "included";
  :>> fpv = "included";
  :>> gps = "included";
  :>> rx = "RxBundled";
  :>> addedPayloadMass_g = 95.0;
  :>> totalPayloadPower_W = 16.93;
  :>> allUpMass_g = 1743.0;
  :>> hoverPower_W = 231.2;
  :>> maxFlightTimeHover_min = 57.2;
  :>> flightTimeCruise_min = 58.7;
  :>> flightTimeHeadwind_min = 70.4;
  :>> hoverThrottle_pct = 14.9;
  :>> meetsR6_30min = true;
  :>> meetsR8_60min = false;
  :>> flyable = true;
  :>> droneCost_USD = 1486.99;
  :>> gcsCost_USD = 175.45;
  :>> totalSystemCost_USD = 1662.44;
  :>> endurancePer1000USD = 34.39;
  :>> meetsBudgetR4 = true;
 }

 part inst_C000026 : FlightTimeResult {
  :>> configId = "C000026";
  :>> airframeId = "AF4a";
  :>> airframe = "DarwinFPV X9";
  :>> battery = "Upgrade Energy GREEN V2 6S3P 12Ah Amprius SA10";
  :>> chemistry = "Li-ion";
  :>> cellCountS = 6;
  :>> capacity_mAh = 12000.0;
  :>> packVoltage_V = 21.6;
  :>> batteryMass_g = 919.0;
  :>> usableEnergy_Wh = 220.3;
  :>> thermalCam = "T13";
  :>> sbc = "SBC3";
  :>> dvr = "—";
  :>> vtx = "included";
  :>> fpv = "included";
  :>> gps = "GpsBundled";
  :>> rx = "RxBundled";
  :>> addedPayloadMass_g = 95.0;
  :>> totalPayloadPower_W = 16.93;
  :>> allUpMass_g = 1761.0;
  :>> hoverPower_W = 234.5;
  :>> maxFlightTimeHover_min = 56.4;
  :>> flightTimeCruise_min = 57.9;
  :>> flightTimeHeadwind_min = 69.5;
  :>> hoverThrottle_pct = 13.6;
  :>> meetsR6_30min = true;
  :>> meetsR8_60min = false;
  :>> flyable = true;
  :>> droneCost_USD = 1412.99;
  :>> gcsCost_USD = 175.45;
  :>> totalSystemCost_USD = 1588.44;
  :>> endurancePer1000USD = 35.48;
  :>> meetsBudgetR4 = true;
 }

 part inst_C000003 : FlightTimeResult {
  :>> configId = "C000003";
  :>> airframeId = "AF3a";
  :>> airframe = "iFlight Chimera9 ECO";
  :>> battery = "Upgrade Energy RED V3 6S2P 10Ah Molicel P50B";
  :>> chemistry = "Li-ion";
  :>> cellCountS = 6;
  :>> capacity_mAh = 10000.0;
  :>> packVoltage_V = 21.6;
  :>> batteryMass_g = 868.0;
  :>> usableEnergy_Wh = 183.6;
  :>> thermalCam = "T13";
  :>> sbc = "SBC3";
  :>> dvr = "—";
  :>> vtx = "included";
  :>> fpv = "included";
  :>> gps = "included";
  :>> rx = "RxBundled";
  :>> addedPayloadMass_g = 95.0;
  :>> totalPayloadPower_W = 16.93;
  :>> allUpMass_g = 1692.0;
  :>> hoverPower_W = 221.9;
  :>> maxFlightTimeHover_min = 49.6;
  :>> flightTimeCruise_min = 51.0;
  :>> flightTimeHeadwind_min = 61.4;
  :>> hoverThrottle_pct = 14.4;
  :>> meetsR6_30min = true;
  :>> meetsR8_60min = false;
  :>> flyable = true;
  :>> droneCost_USD = 1463.99;
  :>> gcsCost_USD = 175.45;
  :>> totalSystemCost_USD = 1639.44;
  :>> endurancePer1000USD = 30.28;
  :>> meetsBudgetR4 = true;
 }

 part inst_C000006 : FlightTimeResult {
  :>> configId = "C000006";
  :>> airframeId = "AF3a";
  :>> airframe = "iFlight Chimera9 ECO";
  :>> battery = "Upgrade Energy GREEN V2 6S2P 8Ah Amprius SA10";
  :>> chemistry = "Li-ion";
  :>> cellCountS = 6;
  :>> capacity_mAh = 8000.0;
  :>> packVoltage_V = 21.6;
  :>> batteryMass_g = 617.0;
  :>> usableEnergy_Wh = 146.9;
  :>> thermalCam = "T13";
  :>> sbc = "SBC3";
  :>> dvr = "—";
  :>> vtx = "included";
  :>> fpv = "included";
  :>> gps = "included";
  :>> rx = "RxBundled";
  :>> addedPayloadMass_g = 95.0;
  :>> totalPayloadPower_W = 16.93;
  :>> allUpMass_g = 1441.0;
  :>> hoverPower_W = 178.0;
  :>> maxFlightTimeHover_min = 49.5;
  :>> flightTimeCruise_min = 51.1;
  :>> flightTimeHeadwind_min = 62.6;
  :>> hoverThrottle_pct = 12.3;
  :>> meetsR6_30min = true;
  :>> meetsR8_60min = false;
  :>> flyable = true;
  :>> droneCost_USD = 1405.99;
  :>> gcsCost_USD = 175.45;
  :>> totalSystemCost_USD = 1581.44;
  :>> endurancePer1000USD = 31.31;
  :>> meetsBudgetR4 = true;
 }

 part inst_C000020 : FlightTimeResult {
  :>> configId = "C000020";
  :>> airframeId = "AF4a";
  :>> airframe = "DarwinFPV X9";
  :>> battery = "Upgrade Energy RED V3 6S2P 10Ah Molicel P50B";
  :>> chemistry = "Li-ion";
  :>> cellCountS = 6;
  :>> capacity_mAh = 10000.0;
  :>> packVoltage_V = 21.6;
  :>> batteryMass_g = 868.0;
  :>> usableEnergy_Wh = 183.6;
  :>> thermalCam = "T13";
  :>> sbc = "SBC3";
  :>> dvr = "—";
  :>> vtx = "included";
  :>> fpv = "included";
  :>> gps = "GpsBundled";
  :>> rx = "RxBundled";
  :>> addedPayloadMass_g = 95.0;
  :>> totalPayloadPower_W = 16.93;
  :>> allUpMass_g = 1710.0;
  :>> hoverPower_W = 225.2;
  :>> maxFlightTimeHover_min = 48.9;
  :>> flightTimeCruise_min = 50.3;
  :>> flightTimeHeadwind_min = 60.6;
  :>> hoverThrottle_pct = 13.2;
  :>> meetsR6_30min = true;
  :>> meetsR8_60min = false;
  :>> flyable = true;
  :>> droneCost_USD = 1389.99;
  :>> gcsCost_USD = 175.45;
  :>> totalSystemCost_USD = 1565.44;
  :>> endurancePer1000USD = 31.25;
  :>> meetsBudgetR4 = true;
 }

 part inst_C000023 : FlightTimeResult {
  :>> configId = "C000023";
  :>> airframeId = "AF4a";
  :>> airframe = "DarwinFPV X9";
  :>> battery = "Upgrade Energy GREEN V2 6S2P 8Ah Amprius SA10";
  :>> chemistry = "Li-ion";
  :>> cellCountS = 6;
  :>> capacity_mAh = 8000.0;
  :>> packVoltage_V = 21.6;
  :>> batteryMass_g = 617.0;
  :>> usableEnergy_Wh = 146.9;
  :>> thermalCam = "T13";
  :>> sbc = "SBC3";
  :>> dvr = "—";
  :>> vtx = "included";
  :>> fpv = "included";
  :>> gps = "GpsBundled";
  :>> rx = "RxBundled";
  :>> addedPayloadMass_g = 95.0;
  :>> totalPayloadPower_W = 16.93;
  :>> allUpMass_g = 1459.0;
  :>> hoverPower_W = 181.0;
  :>> maxFlightTimeHover_min = 48.7;
  :>> flightTimeCruise_min = 50.2;
  :>> flightTimeHeadwind_min = 61.7;
  :>> hoverThrottle_pct = 11.2;
  :>> meetsR6_30min = true;
  :>> meetsR8_60min = false;
  :>> flyable = true;
  :>> droneCost_USD = 1331.99;
  :>> gcsCost_USD = 175.45;
  :>> totalSystemCost_USD = 1507.44;
  :>> endurancePer1000USD = 32.29;
  :>> meetsBudgetR4 = true;
 }

 part inst_C000002 : FlightTimeResult {
  :>> configId = "C000002";
  :>> airframeId = "AF3a";
  :>> airframe = "iFlight Chimera9 ECO";
  :>> battery = "Upgrade Energy GREEN V1 6S2P 10Ah Samsung 50S";
  :>> chemistry = "Li-ion";
  :>> cellCountS = 6;
  :>> capacity_mAh = 10000.0;
  :>> packVoltage_V = 21.6;
  :>> batteryMass_g = 900.0;
  :>> usableEnergy_Wh = 183.6;
  :>> thermalCam = "T13";
  :>> sbc = "SBC3";
  :>> dvr = "—";
  :>> vtx = "included";
  :>> fpv = "included";
  :>> gps = "included";
  :>> rx = "RxBundled";
  :>> addedPayloadMass_g = 95.0;
  :>> totalPayloadPower_W = 16.93;
  :>> allUpMass_g = 1724.0;
  :>> hoverPower_W = 227.7;
  :>> maxFlightTimeHover_min = 48.4;
  :>> flightTimeCruise_min = 49.7;
  :>> flightTimeHeadwind_min = 59.6;
  :>> hoverThrottle_pct = 14.7;
  :>> meetsR6_30min = true;
  :>> meetsR8_60min = false;
  :>> flyable = true;
  :>> droneCost_USD = 1481.98;
  :>> gcsCost_USD = 175.45;
  :>> totalSystemCost_USD = 1657.43;
  :>> endurancePer1000USD = 29.19;
  :>> meetsBudgetR4 = true;
 }

 part inst_C000019 : FlightTimeResult {
  :>> configId = "C000019";
  :>> airframeId = "AF4a";
  :>> airframe = "DarwinFPV X9";
  :>> battery = "Upgrade Energy GREEN V1 6S2P 10Ah Samsung 50S";
  :>> chemistry = "Li-ion";
  :>> cellCountS = 6;
  :>> capacity_mAh = 10000.0;
  :>> packVoltage_V = 21.6;
  :>> batteryMass_g = 900.0;
  :>> usableEnergy_Wh = 183.6;
  :>> thermalCam = "T13";
  :>> sbc = "SBC3";
  :>> dvr = "—";
  :>> vtx = "included";
  :>> fpv = "included";
  :>> gps = "GpsBundled";
  :>> rx = "RxBundled";
  :>> addedPayloadMass_g = 95.0;
  :>> totalPayloadPower_W = 16.93;
  :>> allUpMass_g = 1742.0;
  :>> hoverPower_W = 231.0;
  :>> maxFlightTimeHover_min = 47.7;
  :>> flightTimeCruise_min = 49.0;
  :>> flightTimeHeadwind_min = 58.9;
  :>> hoverThrottle_pct = 13.4;
  :>> meetsR6_30min = true;
  :>> meetsR8_60min = false;
  :>> flyable = true;
  :>> droneCost_USD = 1407.98;
  :>> gcsCost_USD = 175.45;
  :>> totalSystemCost_USD = 1583.43;
  :>> endurancePer1000USD = 30.11;
  :>> meetsBudgetR4 = true;
 }

 part inst_C000001 : FlightTimeResult {
  :>> configId = "C000001";
  :>> airframeId = "AF3a";
  :>> airframe = "iFlight Chimera9 ECO";
  :>> battery = "Lumenier NAV 10000mAh 6S 21700 Li-Ion";
  :>> chemistry = "Li-ion";
  :>> cellCountS = 6;
  :>> capacity_mAh = 10000.0;
  :>> packVoltage_V = 22.2;
  :>> batteryMass_g = 975.0;
  :>> usableEnergy_Wh = 188.7;
  :>> thermalCam = "T13";
  :>> sbc = "SBC3";
  :>> dvr = "—";
  :>> vtx = "included";
  :>> fpv = "included";
  :>> gps = "included";
  :>> rx = "RxBundled";
  :>> addedPayloadMass_g = 95.0;
  :>> totalPayloadPower_W = 16.93;
  :>> allUpMass_g = 1799.0;
  :>> hoverPower_W = 241.6;
  :>> maxFlightTimeHover_min = 46.9;
  :>> flightTimeCruise_min = 48.1;
  :>> flightTimeHeadwind_min = 57.4;
  :>> hoverThrottle_pct = 15.3;
  :>> meetsR6_30min = true;
  :>> meetsR8_60min = false;
  :>> flyable = true;
  :>> droneCost_USD = 1361.98;
  :>> gcsCost_USD = 175.45;
  :>> totalSystemCost_USD = 1537.43;
  :>> endurancePer1000USD = 30.48;
  :>> meetsBudgetR4 = true;
 }

 part inst_C000018 : FlightTimeResult {
  :>> configId = "C000018";
  :>> airframeId = "AF4a";
  :>> airframe = "DarwinFPV X9";
  :>> battery = "Lumenier NAV 10000mAh 6S 21700 Li-Ion";
  :>> chemistry = "Li-ion";
  :>> cellCountS = 6;
  :>> capacity_mAh = 10000.0;
  :>> packVoltage_V = 22.2;
  :>> batteryMass_g = 975.0;
  :>> usableEnergy_Wh = 188.7;
  :>> thermalCam = "T13";
  :>> sbc = "SBC3";
  :>> dvr = "—";
  :>> vtx = "included";
  :>> fpv = "included";
  :>> gps = "GpsBundled";
  :>> rx = "RxBundled";
  :>> addedPayloadMass_g = 95.0;
  :>> totalPayloadPower_W = 16.93;
  :>> allUpMass_g = 1817.0;
  :>> hoverPower_W = 245.0;
  :>> maxFlightTimeHover_min = 46.2;
  :>> flightTimeCruise_min = 47.4;
  :>> flightTimeHeadwind_min = 56.7;
  :>> hoverThrottle_pct = 14.0;
  :>> meetsR6_30min = true;
  :>> meetsR8_60min = false;
  :>> flyable = true;
  :>> droneCost_USD = 1287.98;
  :>> gcsCost_USD = 175.45;
  :>> totalSystemCost_USD = 1463.43;
  :>> endurancePer1000USD = 31.58;
  :>> meetsBudgetR4 = true;
 }

 part inst_C000016 : FlightTimeResult {
  :>> configId = "C000016";
  :>> airframeId = "AF3a";
  :>> airframe = "iFlight Chimera9 ECO";
  :>> battery = "GNB (Gaoneng) 6S3P 12Ah 21700 Li-ion";
  :>> chemistry = "Li-ion";
  :>> cellCountS = 6;
  :>> capacity_mAh = 12000.0;
  :>> packVoltage_V = 22.2;
  :>> batteryMass_g = 1250.0;
  :>> usableEnergy_Wh = 226.4;
  :>> thermalCam = "T13";
  :>> sbc = "SBC3";
  :>> dvr = "—";
  :>> vtx = "included";
  :>> fpv = "included";
  :>> gps = "included";
  :>> rx = "RxBundled";
  :>> addedPayloadMass_g = 95.0;
  :>> totalPayloadPower_W = 16.93;
  :>> allUpMass_g = 2074.0;
  :>> hoverPower_W = 295.1;
  :>> maxFlightTimeHover_min = 46.0;
  :>> flightTimeCruise_min = 47.1;
  :>> flightTimeHeadwind_min = 55.3;
  :>> hoverThrottle_pct = 17.7;
  :>> meetsR6_30min = true;
  :>> meetsR8_60min = false;
  :>> flyable = true;
  :>> droneCost_USD = 1321.99;
  :>> gcsCost_USD = 175.45;
  :>> totalSystemCost_USD = 1497.44;
  :>> endurancePer1000USD = 30.75;
  :>> meetsBudgetR4 = true;
 }

 part inst_C000033 : FlightTimeResult {
  :>> configId = "C000033";
  :>> airframeId = "AF4a";
  :>> airframe = "DarwinFPV X9";
  :>> battery = "GNB (Gaoneng) 6S3P 12Ah 21700 Li-ion";
  :>> chemistry = "Li-ion";
  :>> cellCountS = 6;
  :>> capacity_mAh = 12000.0;
  :>> packVoltage_V = 22.2;
  :>> batteryMass_g = 1250.0;
  :>> usableEnergy_Wh = 226.4;
  :>> thermalCam = "T13";
  :>> sbc = "SBC3";
  :>> dvr = "—";
  :>> vtx = "included";
  :>> fpv = "included";
  :>> gps = "GpsBundled";
  :>> rx = "RxBundled";
  :>> addedPayloadMass_g = 95.0;
  :>> totalPayloadPower_W = 16.93;
  :>> allUpMass_g = 2092.0;
  :>> hoverPower_W = 298.7;
  :>> maxFlightTimeHover_min = 45.5;
  :>> flightTimeCruise_min = 46.5;
  :>> flightTimeHeadwind_min = 54.7;
  :>> hoverThrottle_pct = 16.1;
  :>> meetsR6_30min = true;
  :>> meetsR8_60min = false;
  :>> flyable = true;
  :>> droneCost_USD = 1247.99;
  :>> gcsCost_USD = 175.45;
  :>> totalSystemCost_USD = 1423.44;
  :>> endurancePer1000USD = 31.95;
  :>> meetsBudgetR4 = true;
 }

 part inst_C000005 : FlightTimeResult {
  :>> configId = "C000005";
  :>> airframeId = "AF3a";
  :>> airframe = "iFlight Chimera9 ECO";
  :>> battery = "iFlight Fullsend 6S 8000mAh EVE INR21700-40PL";
  :>> chemistry = "Li-ion";
  :>> cellCountS = 6;
  :>> capacity_mAh = 8000.0;
  :>> packVoltage_V = 22.2;
  :>> batteryMass_g = 840.0;
  :>> usableEnergy_Wh = 151.0;
  :>> thermalCam = "T13";
  :>> sbc = "SBC3";
  :>> dvr = "—";
  :>> vtx = "included";
  :>> fpv = "included";
  :>> gps = "included";
  :>> rx = "RxBundled";
  :>> addedPayloadMass_g = 95.0;
  :>> totalPayloadPower_W = 16.93;
  :>> allUpMass_g = 1664.0;
  :>> hoverPower_W = 216.8;
  :>> maxFlightTimeHover_min = 41.8;
  :>> flightTimeCruise_min = 42.9;
  :>> flightTimeHeadwind_min = 51.8;
  :>> hoverThrottle_pct = 14.2;
  :>> meetsR6_30min = true;
  :>> meetsR8_60min = false;
  :>> flyable = true;
  :>> droneCost_USD = 1334.98;
  :>> gcsCost_USD = 175.45;
  :>> totalSystemCost_USD = 1510.43;
  :>> endurancePer1000USD = 27.66;
  :>> meetsBudgetR4 = true;
 }

 part inst_C000007 : FlightTimeResult {
  :>> configId = "C000007";
  :>> airframeId = "AF3a";
  :>> airframe = "iFlight Chimera9 ECO";
  :>> battery = "Lumenier NAV 12000mAh 6S 21700 XT90";
  :>> chemistry = "Li-ion";
  :>> cellCountS = 6;
  :>> capacity_mAh = 12000.0;
  :>> packVoltage_V = 22.2;
  :>> batteryMass_g = 1402.0;
  :>> usableEnergy_Wh = 226.4;
  :>> thermalCam = "T13";
  :>> sbc = "SBC3";
  :>> dvr = "—";
  :>> vtx = "included";
  :>> fpv = "included";
  :>> gps = "included";
  :>> rx = "RxBundled";
  :>> addedPayloadMass_g = 95.0;
  :>> totalPayloadPower_W = 16.93;
  :>> allUpMass_g = 2226.0;
  :>> hoverPower_W = 326.2;
  :>> maxFlightTimeHover_min = 41.7;
  :>> flightTimeCruise_min = 42.5;
  :>> flightTimeHeadwind_min = 49.5;
  :>> hoverThrottle_pct = 19.0;
  :>> meetsR6_30min = true;
  :>> meetsR8_60min = false;
  :>> flyable = true;
  :>> droneCost_USD = 1401.98;
  :>> gcsCost_USD = 175.45;
  :>> totalSystemCost_USD = 1577.43;
  :>> endurancePer1000USD = 26.4;
  :>> meetsBudgetR4 = true;
 }

 part inst_C000022 : FlightTimeResult {
  :>> configId = "C000022";
  :>> airframeId = "AF4a";
  :>> airframe = "DarwinFPV X9";
  :>> battery = "iFlight Fullsend 6S 8000mAh EVE INR21700-40PL";
  :>> chemistry = "Li-ion";
  :>> cellCountS = 6;
  :>> capacity_mAh = 8000.0;
  :>> packVoltage_V = 22.2;
  :>> batteryMass_g = 840.0;
  :>> usableEnergy_Wh = 151.0;
  :>> thermalCam = "T13";
  :>> sbc = "SBC3";
  :>> dvr = "—";
  :>> vtx = "included";
  :>> fpv = "included";
  :>> gps = "GpsBundled";
  :>> rx = "RxBundled";
  :>> addedPayloadMass_g = 95.0;
  :>> totalPayloadPower_W = 16.93;
  :>> allUpMass_g = 1682.0;
  :>> hoverPower_W = 220.1;
  :>> maxFlightTimeHover_min = 41.2;
  :>> flightTimeCruise_min = 42.3;
  :>> flightTimeHeadwind_min = 51.1;
  :>> hoverThrottle_pct = 13.0;
  :>> meetsR6_30min = true;
  :>> meetsR8_60min = false;
  :>> flyable = true;
  :>> droneCost_USD = 1260.98;
  :>> gcsCost_USD = 175.45;
  :>> totalSystemCost_USD = 1436.43;
  :>> endurancePer1000USD = 28.65;
  :>> meetsBudgetR4 = true;
 }

 part inst_C000024 : FlightTimeResult {
  :>> configId = "C000024";
  :>> airframeId = "AF4a";
  :>> airframe = "DarwinFPV X9";
  :>> battery = "Lumenier NAV 12000mAh 6S 21700 XT90";
  :>> chemistry = "Li-ion";
  :>> cellCountS = 6;
  :>> capacity_mAh = 12000.0;
  :>> packVoltage_V = 22.2;
  :>> batteryMass_g = 1402.0;
  :>> usableEnergy_Wh = 226.4;
  :>> thermalCam = "T13";
  :>> sbc = "SBC3";
  :>> dvr = "—";
  :>> vtx = "included";
  :>> fpv = "included";
  :>> gps = "GpsBundled";
  :>> rx = "RxBundled";
  :>> addedPayloadMass_g = 95.0;
  :>> totalPayloadPower_W = 16.93;
  :>> allUpMass_g = 2244.0;
  :>> hoverPower_W = 330.0;
  :>> maxFlightTimeHover_min = 41.2;
  :>> flightTimeCruise_min = 42.1;
  :>> flightTimeHeadwind_min = 49.0;
  :>> hoverThrottle_pct = 17.3;
  :>> meetsR6_30min = true;
  :>> meetsR8_60min = false;
  :>> flyable = true;
  :>> droneCost_USD = 1327.98;
  :>> gcsCost_USD = 175.45;
  :>> totalSystemCost_USD = 1503.43;
  :>> endurancePer1000USD = 27.39;
  :>> meetsBudgetR4 = true;
 }

 part inst_C000004 : FlightTimeResult {
  :>> configId = "C000004";
  :>> airframeId = "AF3a";
  :>> airframe = "iFlight Chimera9 ECO";
  :>> battery = "GNB 8000mAh 6S2P Samsung 21700 40T";
  :>> chemistry = "Li-ion";
  :>> cellCountS = 6;
  :>> capacity_mAh = 8000.0;
  :>> packVoltage_V = 22.2;
  :>> batteryMass_g = 904.0;
  :>> usableEnergy_Wh = 151.0;
  :>> thermalCam = "T13";
  :>> sbc = "SBC3";
  :>> dvr = "—";
  :>> vtx = "included";
  :>> fpv = "included";
  :>> gps = "included";
  :>> rx = "RxBundled";
  :>> addedPayloadMass_g = 95.0;
  :>> totalPayloadPower_W = 16.93;
  :>> allUpMass_g = 1728.0;
  :>> hoverPower_W = 228.5;
  :>> maxFlightTimeHover_min = 39.6;
  :>> flightTimeCruise_min = 40.7;
  :>> flightTimeHeadwind_min = 48.9;
  :>> hoverThrottle_pct = 14.7;
  :>> meetsR6_30min = true;
  :>> meetsR8_60min = false;
  :>> flyable = true;
  :>> droneCost_USD = 1347.98;
  :>> gcsCost_USD = 175.45;
  :>> totalSystemCost_USD = 1523.43;
  :>> endurancePer1000USD = 26.03;
  :>> meetsBudgetR4 = true;
 }

 part inst_C000010 : FlightTimeResult {
  :>> configId = "C000010";
  :>> airframeId = "AF3a";
  :>> airframe = "iFlight Chimera9 ECO";
  :>> battery = "Pyrodrone Hyperjuice 6S2P 6000mAh Sony VTC6";
  :>> chemistry = "Li-ion";
  :>> cellCountS = 6;
  :>> capacity_mAh = 6000.0;
  :>> packVoltage_V = 22.2;
  :>> batteryMass_g = 590.0;
  :>> usableEnergy_Wh = 113.2;
  :>> thermalCam = "T13";
  :>> sbc = "SBC3";
  :>> dvr = "—";
  :>> vtx = "included";
  :>> fpv = "included";
  :>> gps = "included";
  :>> rx = "RxBundled";
  :>> addedPayloadMass_g = 95.0;
  :>> totalPayloadPower_W = 16.93;
  :>> allUpMass_g = 1414.0;
  :>> hoverPower_W = 173.5;
  :>> maxFlightTimeHover_min = 39.2;
  :>> flightTimeCruise_min = 40.4;
  :>> flightTimeHeadwind_min = 49.6;
  :>> hoverThrottle_pct = 12.1;
  :>> meetsR6_30min = true;
  :>> meetsR8_60min = false;
  :>> flyable = true;
  :>> droneCost_USD = 1384.98;
  :>> gcsCost_USD = 175.45;
  :>> totalSystemCost_USD = 1560.43;
  :>> endurancePer1000USD = 25.09;
  :>> meetsBudgetR4 = true;
 }

 part inst_C000021 : FlightTimeResult {
  :>> configId = "C000021";
  :>> airframeId = "AF4a";
  :>> airframe = "DarwinFPV X9";
  :>> battery = "GNB 8000mAh 6S2P Samsung 21700 40T";
  :>> chemistry = "Li-ion";
  :>> cellCountS = 6;
  :>> capacity_mAh = 8000.0;
  :>> packVoltage_V = 22.2;
  :>> batteryMass_g = 904.0;
  :>> usableEnergy_Wh = 151.0;
  :>> thermalCam = "T13";
  :>> sbc = "SBC3";
  :>> dvr = "—";
  :>> vtx = "included";
  :>> fpv = "included";
  :>> gps = "GpsBundled";
  :>> rx = "RxBundled";
  :>> addedPayloadMass_g = 95.0;
  :>> totalPayloadPower_W = 16.93;
  :>> allUpMass_g = 1746.0;
  :>> hoverPower_W = 231.8;
  :>> maxFlightTimeHover_min = 39.1;
  :>> flightTimeCruise_min = 40.1;
  :>> flightTimeHeadwind_min = 48.2;
  :>> hoverThrottle_pct = 13.5;
  :>> meetsR6_30min = true;
  :>> meetsR8_60min = false;
  :>> flyable = true;
  :>> droneCost_USD = 1273.98;
  :>> gcsCost_USD = 175.45;
  :>> totalSystemCost_USD = 1449.43;
  :>> endurancePer1000USD = 26.96;
  :>> meetsBudgetR4 = true;
 }

 part inst_C000011 : FlightTimeResult {
  :>> configId = "C000011";
  :>> airframeId = "AF3a";
  :>> airframe = "iFlight Chimera9 ECO";
  :>> battery = "iFlight Fullsend 6S2P 6000mAh Samsung 30Q";
  :>> chemistry = "Li-ion";
  :>> cellCountS = 6;
  :>> capacity_mAh = 6000.0;
  :>> packVoltage_V = 22.2;
  :>> batteryMass_g = 608.0;
  :>> usableEnergy_Wh = 113.2;
  :>> thermalCam = "T13";
  :>> sbc = "SBC3";
  :>> dvr = "—";
  :>> vtx = "included";
  :>> fpv = "included";
  :>> gps = "included";
  :>> rx = "RxBundled";
  :>> addedPayloadMass_g = 95.0;
  :>> totalPayloadPower_W = 16.93;
  :>> allUpMass_g = 1432.0;
  :>> hoverPower_W = 176.5;
  :>> maxFlightTimeHover_min = 38.5;
  :>> flightTimeCruise_min = 39.7;
  :>> flightTimeHeadwind_min = 48.7;
  :>> hoverThrottle_pct = 12.2;
  :>> meetsR6_30min = true;
  :>> meetsR8_60min = false;
  :>> flyable = true;
  :>> droneCost_USD = 1296.46;
  :>> gcsCost_USD = 175.45;
  :>> totalSystemCost_USD = 1471.91;
  :>> endurancePer1000USD = 26.15;
  :>> meetsBudgetR4 = true;
 }

 part inst_C000027 : FlightTimeResult {
  :>> configId = "C000027";
  :>> airframeId = "AF4a";
  :>> airframe = "DarwinFPV X9";
  :>> battery = "Pyrodrone Hyperjuice 6S2P 6000mAh Sony VTC6";
  :>> chemistry = "Li-ion";
  :>> cellCountS = 6;
  :>> capacity_mAh = 6000.0;
  :>> packVoltage_V = 22.2;
  :>> batteryMass_g = 590.0;
  :>> usableEnergy_Wh = 113.2;
  :>> thermalCam = "T13";
  :>> sbc = "SBC3";
  :>> dvr = "—";
  :>> vtx = "included";
  :>> fpv = "included";
  :>> gps = "GpsBundled";
  :>> rx = "RxBundled";
  :>> addedPayloadMass_g = 95.0;
  :>> totalPayloadPower_W = 16.93;
  :>> allUpMass_g = 1432.0;
  :>> hoverPower_W = 176.5;
  :>> maxFlightTimeHover_min = 38.5;
  :>> flightTimeCruise_min = 39.7;
  :>> flightTimeHeadwind_min = 48.9;
  :>> hoverThrottle_pct = 11.0;
  :>> meetsR6_30min = true;
  :>> meetsR8_60min = false;
  :>> flyable = true;
  :>> droneCost_USD = 1310.98;
  :>> gcsCost_USD = 175.45;
  :>> totalSystemCost_USD = 1486.43;
  :>> endurancePer1000USD = 25.89;
  :>> meetsBudgetR4 = true;
 }

 part inst_C000017 : FlightTimeResult {
  :>> configId = "C000017";
  :>> airframeId = "AF3a";
  :>> airframe = "iFlight Chimera9 ECO";
  :>> battery = "Tattu G-Tech 6S 12Ah LiPo 30C";
  :>> chemistry = "LiPo";
  :>> cellCountS = 6;
  :>> capacity_mAh = 12000.0;
  :>> packVoltage_V = 22.2;
  :>> batteryMass_g = 1532.0;
  :>> usableEnergy_Wh = 226.4;
  :>> thermalCam = "T13";
  :>> sbc = "SBC3";
  :>> dvr = "—";
  :>> vtx = "included";
  :>> fpv = "included";
  :>> gps = "included";
  :>> rx = "RxBundled";
  :>> addedPayloadMass_g = 95.0;
  :>> totalPayloadPower_W = 16.93;
  :>> allUpMass_g = 2356.0;
  :>> hoverPower_W = 353.7;
  :>> maxFlightTimeHover_min = 38.4;
  :>> flightTimeCruise_min = 39.2;
  :>> flightTimeHeadwind_min = 45.3;
  :>> hoverThrottle_pct = 20.1;
  :>> meetsR6_30min = true;
  :>> meetsR8_60min = false;
  :>> flyable = true;
  :>> droneCost_USD = 1361.98;
  :>> gcsCost_USD = 175.45;
  :>> totalSystemCost_USD = 1537.43;
  :>> endurancePer1000USD = 24.99;
  :>> meetsBudgetR4 = true;
 }

 part inst_C000034 : FlightTimeResult {
  :>> configId = "C000034";
  :>> airframeId = "AF4a";
  :>> airframe = "DarwinFPV X9";
  :>> battery = "Tattu G-Tech 6S 12Ah LiPo 30C";
  :>> chemistry = "LiPo";
  :>> cellCountS = 6;
  :>> capacity_mAh = 12000.0;
  :>> packVoltage_V = 22.2;
  :>> batteryMass_g = 1532.0;
  :>> usableEnergy_Wh = 226.4;
  :>> thermalCam = "T13";
  :>> sbc = "SBC3";
  :>> dvr = "—";
  :>> vtx = "included";
  :>> fpv = "included";
  :>> gps = "GpsBundled";
  :>> rx = "RxBundled";
  :>> addedPayloadMass_g = 95.0;
  :>> totalPayloadPower_W = 16.93;
  :>> allUpMass_g = 2374.0;
  :>> hoverPower_W = 357.5;
  :>> maxFlightTimeHover_min = 38.0;
  :>> flightTimeCruise_min = 38.8;
  :>> flightTimeHeadwind_min = 44.9;
  :>> hoverThrottle_pct = 18.3;
  :>> meetsR6_30min = true;
  :>> meetsR8_60min = false;
  :>> flyable = true;
  :>> droneCost_USD = 1287.98;
  :>> gcsCost_USD = 175.45;
  :>> totalSystemCost_USD = 1463.43;
  :>> endurancePer1000USD = 25.97;
  :>> meetsBudgetR4 = true;
 }

 part inst_C000028 : FlightTimeResult {
  :>> configId = "C000028";
  :>> airframeId = "AF4a";
  :>> airframe = "DarwinFPV X9";
  :>> battery = "iFlight Fullsend 6S2P 6000mAh Samsung 30Q";
  :>> chemistry = "Li-ion";
  :>> cellCountS = 6;
  :>> capacity_mAh = 6000.0;
  :>> packVoltage_V = 22.2;
  :>> batteryMass_g = 608.0;
  :>> usableEnergy_Wh = 113.2;
  :>> thermalCam = "T13";
  :>> sbc = "SBC3";
  :>> dvr = "—";
  :>> vtx = "included";
  :>> fpv = "included";
  :>> gps = "GpsBundled";
  :>> rx = "RxBundled";
  :>> addedPayloadMass_g = 95.0;
  :>> totalPayloadPower_W = 16.93;
  :>> allUpMass_g = 1450.0;
  :>> hoverPower_W = 179.5;
  :>> maxFlightTimeHover_min = 37.8;
  :>> flightTimeCruise_min = 39.0;
  :>> flightTimeHeadwind_min = 48.0;
  :>> hoverThrottle_pct = 11.2;
  :>> meetsR6_30min = true;
  :>> meetsR8_60min = false;
  :>> flyable = true;
  :>> droneCost_USD = 1222.46;
  :>> gcsCost_USD = 175.45;
  :>> totalSystemCost_USD = 1397.91;
  :>> endurancePer1000USD = 27.07;
  :>> meetsBudgetR4 = true;
 }

 part inst_C000015 : FlightTimeResult {
  :>> configId = "C000015";
  :>> airframeId = "AF3a";
  :>> airframe = "iFlight Chimera9 ECO";
  :>> battery = "DOGCOM 6S1P 5000mAh Samsung 50S";
  :>> chemistry = "Li-ion";
  :>> cellCountS = 6;
  :>> capacity_mAh = 5000.0;
  :>> packVoltage_V = 22.2;
  :>> batteryMass_g = 445.0;
  :>> usableEnergy_Wh = 94.3;
  :>> thermalCam = "T13";
  :>> sbc = "SBC3";
  :>> dvr = "—";
  :>> vtx = "included";
  :>> fpv = "included";
  :>> gps = "included";
  :>> rx = "RxBundled";
  :>> addedPayloadMass_g = 95.0;
  :>> totalPayloadPower_W = 16.93;
  :>> allUpMass_g = 1269.0;
  :>> hoverPower_W = 150.0;
  :>> maxFlightTimeHover_min = 37.7;
  :>> flightTimeCruise_min = 39.0;
  :>> flightTimeHeadwind_min = 48.5;
  :>> hoverThrottle_pct = 10.8;
  :>> meetsR6_30min = true;
  :>> meetsR8_60min = false;
  :>> flyable = true;
  :>> droneCost_USD = 1261.99;
  :>> gcsCost_USD = 175.45;
  :>> totalSystemCost_USD = 1437.44;
  :>> endurancePer1000USD = 26.25;
  :>> meetsBudgetR4 = true;
 }

 part inst_C000012 : FlightTimeResult {
  :>> configId = "C000012";
  :>> airframeId = "AF3a";
  :>> airframe = "iFlight Chimera9 ECO";
  :>> battery = "Lumenier NAV 6000mAh 6S 18650";
  :>> chemistry = "Li-ion";
  :>> cellCountS = 6;
  :>> capacity_mAh = 6000.0;
  :>> packVoltage_V = 22.2;
  :>> batteryMass_g = 635.0;
  :>> usableEnergy_Wh = 113.2;
  :>> thermalCam = "T13";
  :>> sbc = "SBC3";
  :>> dvr = "—";
  :>> vtx = "included";
  :>> fpv = "included";
  :>> gps = "included";
  :>> rx = "RxBundled";
  :>> addedPayloadMass_g = 95.0;
  :>> totalPayloadPower_W = 16.93;
  :>> allUpMass_g = 1459.0;
  :>> hoverPower_W = 181.0;
  :>> maxFlightTimeHover_min = 37.5;
  :>> flightTimeCruise_min = 38.7;
  :>> flightTimeHeadwind_min = 47.4;
  :>> hoverThrottle_pct = 12.4;
  :>> meetsR6_30min = true;
  :>> meetsR8_60min = false;
  :>> flyable = true;
  :>> droneCost_USD = 1400.98;
  :>> gcsCost_USD = 175.45;
  :>> totalSystemCost_USD = 1576.43;
  :>> endurancePer1000USD = 23.8;
  :>> meetsBudgetR4 = true;
 }

 part inst_C000014 : FlightTimeResult {
  :>> configId = "C000014";
  :>> airframeId = "AF3a";
  :>> airframe = "iFlight Chimera9 ECO";
  :>> battery = "Upgrade Energy RED V3 6S1P 5Ah Molicel P50B";
  :>> chemistry = "Li-ion";
  :>> cellCountS = 6;
  :>> capacity_mAh = 5000.0;
  :>> packVoltage_V = 21.6;
  :>> batteryMass_g = 432.0;
  :>> usableEnergy_Wh = 91.8;
  :>> thermalCam = "T13";
  :>> sbc = "SBC3";
  :>> dvr = "—";
  :>> vtx = "included";
  :>> fpv = "included";
  :>> gps = "included";
  :>> rx = "RxBundled";
  :>> addedPayloadMass_g = 95.0;
  :>> totalPayloadPower_W = 16.93;
  :>> allUpMass_g = 1256.0;
  :>> hoverPower_W = 148.0;
  :>> maxFlightTimeHover_min = 37.2;
  :>> flightTimeCruise_min = 38.5;
  :>> flightTimeHeadwind_min = 47.9;
  :>> hoverThrottle_pct = 10.7;
  :>> meetsR6_30min = true;
  :>> meetsR8_60min = false;
  :>> flyable = true;
  :>> droneCost_USD = 1330.99;
  :>> gcsCost_USD = 175.45;
  :>> totalSystemCost_USD = 1506.44;
  :>> endurancePer1000USD = 24.7;
  :>> meetsBudgetR4 = true;
 }

 part inst_C000032 : FlightTimeResult {
  :>> configId = "C000032";
  :>> airframeId = "AF4a";
  :>> airframe = "DarwinFPV X9";
  :>> battery = "DOGCOM 6S1P 5000mAh Samsung 50S";
  :>> chemistry = "Li-ion";
  :>> cellCountS = 6;
  :>> capacity_mAh = 5000.0;
  :>> packVoltage_V = 22.2;
  :>> batteryMass_g = 445.0;
  :>> usableEnergy_Wh = 94.3;
  :>> thermalCam = "T13";
  :>> sbc = "SBC3";
  :>> dvr = "—";
  :>> vtx = "included";
  :>> fpv = "included";
  :>> gps = "GpsBundled";
  :>> rx = "RxBundled";
  :>> addedPayloadMass_g = 95.0;
  :>> totalPayloadPower_W = 16.93;
  :>> allUpMass_g = 1287.0;
  :>> hoverPower_W = 152.9;
  :>> maxFlightTimeHover_min = 37.0;
  :>> flightTimeCruise_min = 38.3;
  :>> flightTimeHeadwind_min = 47.8;
  :>> hoverThrottle_pct = 9.9;
  :>> meetsR6_30min = true;
  :>> meetsR8_60min = false;
  :>> flyable = true;
  :>> droneCost_USD = 1187.99;
  :>> gcsCost_USD = 175.45;
  :>> totalSystemCost_USD = 1363.44;
  :>> endurancePer1000USD = 27.16;
  :>> meetsBudgetR4 = true;
 }

 part inst_C000029 : FlightTimeResult {
  :>> configId = "C000029";
  :>> airframeId = "AF4a";
  :>> airframe = "DarwinFPV X9";
  :>> battery = "Lumenier NAV 6000mAh 6S 18650";
  :>> chemistry = "Li-ion";
  :>> cellCountS = 6;
  :>> capacity_mAh = 6000.0;
  :>> packVoltage_V = 22.2;
  :>> batteryMass_g = 635.0;
  :>> usableEnergy_Wh = 113.2;
  :>> thermalCam = "T13";
  :>> sbc = "SBC3";
  :>> dvr = "—";
  :>> vtx = "included";
  :>> fpv = "included";
  :>> gps = "GpsBundled";
  :>> rx = "RxBundled";
  :>> addedPayloadMass_g = 95.0;
  :>> totalPayloadPower_W = 16.93;
  :>> allUpMass_g = 1477.0;
  :>> hoverPower_W = 184.1;
  :>> maxFlightTimeHover_min = 36.9;
  :>> flightTimeCruise_min = 38.0;
  :>> flightTimeHeadwind_min = 46.7;
  :>> hoverThrottle_pct = 11.4;
  :>> meetsR6_30min = true;
  :>> meetsR8_60min = false;
  :>> flyable = true;
  :>> droneCost_USD = 1326.98;
  :>> gcsCost_USD = 175.45;
  :>> totalSystemCost_USD = 1502.43;
  :>> endurancePer1000USD = 24.56;
  :>> meetsBudgetR4 = true;
 }

 part inst_C000031 : FlightTimeResult {
  :>> configId = "C000031";
  :>> airframeId = "AF4a";
  :>> airframe = "DarwinFPV X9";
  :>> battery = "Upgrade Energy RED V3 6S1P 5Ah Molicel P50B";
  :>> chemistry = "Li-ion";
  :>> cellCountS = 6;
  :>> capacity_mAh = 5000.0;
  :>> packVoltage_V = 21.6;
  :>> batteryMass_g = 432.0;
  :>> usableEnergy_Wh = 91.8;
  :>> thermalCam = "T13";
  :>> sbc = "SBC3";
  :>> dvr = "—";
  :>> vtx = "included";
  :>> fpv = "included";
  :>> gps = "GpsBundled";
  :>> rx = "RxBundled";
  :>> addedPayloadMass_g = 95.0;
  :>> totalPayloadPower_W = 16.93;
  :>> allUpMass_g = 1274.0;
  :>> hoverPower_W = 150.8;
  :>> maxFlightTimeHover_min = 36.5;
  :>> flightTimeCruise_min = 37.8;
  :>> flightTimeHeadwind_min = 47.2;
  :>> hoverThrottle_pct = 9.8;
  :>> meetsR6_30min = true;
  :>> meetsR8_60min = false;
  :>> flyable = true;
  :>> droneCost_USD = 1256.99;
  :>> gcsCost_USD = 175.45;
  :>> totalSystemCost_USD = 1432.44;
  :>> endurancePer1000USD = 25.49;
  :>> meetsBudgetR4 = true;
 }

 part inst_C000013 : FlightTimeResult {
  :>> configId = "C000013";
  :>> airframeId = "AF3a";
  :>> airframe = "iFlight Chimera9 ECO";
  :>> battery = "Lumenier NAV 5000mAh 6S 21700";
  :>> chemistry = "Li-ion";
  :>> cellCountS = 6;
  :>> capacity_mAh = 5000.0;
  :>> packVoltage_V = 22.2;
  :>> batteryMass_g = 499.0;
  :>> usableEnergy_Wh = 94.3;
  :>> thermalCam = "T13";
  :>> sbc = "SBC3";
  :>> dvr = "—";
  :>> vtx = "included";
  :>> fpv = "included";
  :>> gps = "included";
  :>> rx = "RxBundled";
  :>> addedPayloadMass_g = 95.0;
  :>> totalPayloadPower_W = 16.93;
  :>> allUpMass_g = 1323.0;
  :>> hoverPower_W = 158.6;
  :>> maxFlightTimeHover_min = 35.7;
  :>> flightTimeCruise_min = 36.9;
  :>> flightTimeHeadwind_min = 45.7;
  :>> hoverThrottle_pct = 11.3;
  :>> meetsR6_30min = true;
  :>> meetsR8_60min = false;
  :>> flyable = true;
  :>> droneCost_USD = 1307.98;
  :>> gcsCost_USD = 175.45;
  :>> totalSystemCost_USD = 1483.43;
  :>> endurancePer1000USD = 24.06;
  :>> meetsBudgetR4 = true;
 }

 part inst_C000030 : FlightTimeResult {
  :>> configId = "C000030";
  :>> airframeId = "AF4a";
  :>> airframe = "DarwinFPV X9";
  :>> battery = "Lumenier NAV 5000mAh 6S 21700";
  :>> chemistry = "Li-ion";
  :>> cellCountS = 6;
  :>> capacity_mAh = 5000.0;
  :>> packVoltage_V = 22.2;
  :>> batteryMass_g = 499.0;
  :>> usableEnergy_Wh = 94.3;
  :>> thermalCam = "T13";
  :>> sbc = "SBC3";
  :>> dvr = "—";
  :>> vtx = "included";
  :>> fpv = "included";
  :>> gps = "GpsBundled";
  :>> rx = "RxBundled";
  :>> addedPayloadMass_g = 95.0;
  :>> totalPayloadPower_W = 16.93;
  :>> allUpMass_g = 1341.0;
  :>> hoverPower_W = 161.5;
  :>> maxFlightTimeHover_min = 35.0;
  :>> flightTimeCruise_min = 36.2;
  :>> flightTimeHeadwind_min = 44.9;
  :>> hoverThrottle_pct = 10.3;
  :>> meetsR6_30min = true;
  :>> meetsR8_60min = false;
  :>> flyable = true;
  :>> droneCost_USD = 1233.98;
  :>> gcsCost_USD = 175.45;
  :>> totalSystemCost_USD = 1409.43;
  :>> endurancePer1000USD = 24.86;
  :>> meetsBudgetR4 = true;
 }

}
